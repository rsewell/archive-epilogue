--
-- AC-TEST-MIB.mib
-- MIB generated by MG-SOFT Visual MIB Builder Version 5.0  Build 250
-- Tuesday, November 30, 2010 at 23:03:18
--

	AC-TEST-MIB DEFINITIONS ::= BEGIN
 
		IMPORTS
			otpExpr			
				FROM OTP-REG			
			OBJECT-GROUP, AGENT-CAPABILITIES			
				FROM SNMPv2-CONF			
			Integer32, OBJECT-TYPE, MODULE-IDENTITY, OBJECT-IDENTITY			
				FROM SNMPv2-SMI;
	
	
		acTestModule MODULE-IDENTITY 
			LAST-UPDATED "201011302230Z"		-- November 30, 2010 at 22:30 GMT
			ORGANIZATION 
				"Ac Test Co."
			CONTACT-INFO 
				"developer@small.company."
			DESCRIPTION 
				"Ac Test module."
			::= { reg 1 }

		
	
--
-- Node definitions
--
	
		acTest OBJECT-IDENTITY
			STATUS current
			DESCRIPTION 
				"Test area."
			::= { otpExpr 4321 }

		
		reg OBJECT-IDENTITY
			STATUS current
			DESCRIPTION 
				"Registrations."
			::= { acTest 1 }

		
		mib OBJECT-IDENTITY
			STATUS current
			DESCRIPTION 
				"Objects."
			::= { acTest 2 }

		
		someObject OBJECT-TYPE
			SYNTAX Integer32
			MAX-ACCESS read-write
			STATUS current
			DESCRIPTION
				"Description."
			::= { mib 1 }

		
		oneMore OBJECT-TYPE
			SYNTAX Integer32
			MAX-ACCESS read-write
			STATUS current
			DESCRIPTION
				"Description."
			::= { mib 2 }

		
		grp OBJECT-IDENTITY
			STATUS current
			DESCRIPTION 
				"Groups
				."
			::= { acTest 3 }

		
		basicGrp OBJECT-GROUP
			OBJECTS { someObject }
			STATUS current
			DESCRIPTION 
				"Basic set of objects."
			::= { grp 1 }

		
		allObjects OBJECT-GROUP
			OBJECTS { someObject, oneMore }
			STATUS current
			DESCRIPTION 
				"Complete set."
			::= { grp 2 }

		
		cap OBJECT-IDENTITY
			STATUS current
			DESCRIPTION 
				"Capabilities."
			::= { acTest 5 }


		basicAgent AGENT-CAPABILITIES
			PRODUCT-RELEASE 
				"Product release v1."
			STATUS current
			DESCRIPTION 
				"Basic agent."
			SUPPORTS AC-TEST-MIB
				INCLUDES { basicGrp }
			::= { cap 1 }

		
		fullAgent AGENT-CAPABILITIES
			PRODUCT-RELEASE 
				"Product release v2."
			STATUS current
			DESCRIPTION 
				"Full featured agent."
			SUPPORTS AC-TEST-MIB
				INCLUDES { allObjects }
			::= { cap 2 }

		
	
	END

--
-- AC-TEST-MIB.mib
--
